package LintMark {
    private import SoftwareItemMetadata::*;

    part def EngineSubsystem {
        doc /* Selects the Markdown files named on the command line, processes them in parallel, optionally rewrites them safely, and reports diagnostics deterministically. */

        metadata info : SoftwareInfo {
            testFiles = ("test/DemaConsulting.LintMark.Tests/Engine/EngineSubsystemTests.cs");
            designFiles = ("docs/design/lintmark/engine.md");
            verificationFiles = ("docs/verification/lintmark/engine.md");
            requirementFiles = ("docs/reqstream/lintmark/engine.yaml");
        }

        part fileDiscovery : FileDiscovery;
        part lintMarkEngine : LintMarkEngine;
        part atomicFileWriter : AtomicFileWriter;
    }
}
